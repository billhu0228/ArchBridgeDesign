(command-s "._xline" "a" "131.511179785185" "-241.494321674109,-98.253156696757" "" "")
(command-s "._xline" "a" "134.217957258602" "-230.485415771604,-88.525918600272" "" "")
(command-s "._xline" "a" "130.965079059996" "-219.989787012339,-79.846944566741" "" "")
(command-s "._xline" "a" "133.016880045181" "-209.984537571669,-72.090894463603" "" "")
(command-s "._xline" "a" "134.897004103186" "-199.980430513620,-64.820270930309" "" "")
(command-s "._xline" "a" "136.590750599160" "-189.977373212576,-58.016032546942" "" "")
(command-s "._xline" "a" "138.089604614698" "-179.975273042917,-51.660371702716" "" "")
(command-s "._xline" "a" "139.390436846085" "-169.974068254232,-45.736683847265" "" "")
(command-s "._xline" "a" "140.494503584357" "-159.973650783300,-40.229475134990" "" "")
(command-s "._xline" "a" "141.406407383321" "-149.973989754915,-35.124390661426" "" "")
(command-s "._xline" "a" "142.133128590105" "-139.974992543459,-30.408097660908" "" "")
(command-s "._xline" "a" "142.683191657593" "-129.976628273726,-26.068312970575" "" "")
(command-s "._xline" "a" "143.065991003458" "-119.978819757700,-22.093717624629" "" "")
(command-s "._xline" "a" "143.291277118962" "-109.981551557779,-18.473972256952" "" "")
(command-s "._xline" "a" "143.368784890313" "-99.984761923552,-15.199645178430" "" "")
(command-s "._xline" "a" "143.307983369427" "-89.988435417414,-12.262220959718" "" "")
(command-s "._xline" "a" "143.117922475139" "-79.992510288954,-9.654047434200" "" "")
(command-s "._xline" "a" "142.807153049090" "-69.996971100569,-7.368342674959" "" "")
(command-s "._xline" "a" "142.383702535888" "-60.001786977053,-5.399158382565" "" "")
(command-s "._xline" "a" "141.855088887906" "-50.006942480803,-3.741371253801" "" "")
(command-s "._xline" "a" "141.228360481728" "-40.012391299009,-2.390661494342" "" "")
(command-s "._xline" "a" "140.510152071886" "-30.018117994070,-1.343511626615" "" "")
(command-s "._xline" "a" "130.647765177513" "-21.108675926924,-0.663697809761" "" "")
(command-s "._xline" "a" "130.174870230025" "-13.311281591654,-0.263777070032" "" "")
(command-s "._xline" "a" "129.651812636175" "-5.514010757208,-0.045247560735" "" "")
(command-s "._xline" "a" "49.169773338472" "5.514597386122,-0.045257189545" "" "")
(command-s "._xline" "a" "48.634608297391" "13.311760157347,-0.263796044181" "" "")
(command-s "._xline" "a" "48.150892858241" "21.109015554190,-0.663719187516" "" "")
(command-s "._xline" "a" "38.449430716284" "30.018735498190,-1.343567009344" "" "")
(command-s "._xline" "a" "37.721470611316" "40.012808114290,-2.390711474080" "" "")
(command-s "._xline" "a" "37.086413901662" "50.007158607245,-3.741403767811" "" "")
(command-s "._xline" "a" "36.550920103340" "60.001848727465,-5.399169581651" "" "")
(command-s "._xline" "a" "36.122071916819" "69.996878474951,-7.368322968779" "" "")
(command-s "._xline" "a" "35.807434358614" "79.992294162512,-9.653994549777" "" "")
(command-s "._xline" "a" "35.615098048816" "89.988095790148,-12.262126792377" "" "")
(command-s "._xline" "a" "35.553696637268" "99.984345108271,-15.199515732581" "" "")
(command-s "._xline" "a" "35.632386064003" "109.981057554483,-18.473801995783" "" "")
(command-s "._xline" "a" "35.860768047645" "119.978279441595,-22.093512496280" "" "")
(command-s "._xline" "a" "36.248739766848" "129.976041644812,-26.068069157372" "" "")
(command-s "._xline" "a" "36.806245628234" "139.974390476942,-30.407825125704" "" "")
(command-s "._xline" "a" "37.542905832565" "149.973387688398,-35.124095114300" "" "")
(command-s "._xline" "a" "38.467499951334" "159.973079591990,-40.229172185784" "" "")
(command-s "._xline" "a" "39.587286124433" "169.973512500525,-45.736366373267" "" "")
(command-s "._xline" "a" "40.907155111310" "179.974779039621,-51.660068583051" "" "")
(command-s "._xline" "a" "42.428642571295" "189.976925522089,-58.015738173142" "" "")
(command-s "._xline" "a" "44.148862707559" "199.980060011148,-64.820010398707" "" "")
(command-s "._xline" "a" "46.059473926349" "209.984263554215,-72.090688771001" "" "")
(command-s "._xline" "a" "48.145839667090" "219.989632636309,-79.846821054436" "" "")
(command-s "._xline" "a" "44.939063917774" "230.485211223364,-88.525743886697" "" "")
(command-s "._xline" "a" "47.686063367041" "241.494259923697,-98.253100289294" "" "")
